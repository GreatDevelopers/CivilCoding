# -*- coding: utf-8 -*-

import FreeCAD
import Part
import Sketcher
import Arch
import math
import re 
import WorkingPlane 

# --- User Input Data for Wall Sketch ---
# Define your wall layout here as a single string.
# Format: "Easting,Northing LengthDirection LengthDirection ... C(optional)"
#   - Easting,Northing: Absolute starting point in the current working plane's XY.
#       (e.g., "0,0" or "-100.5,200")
#   - LengthDirection: Segment definition (no spaces between L and D).
#       - Length (L): Can be positive or negative. If negative, direction is reversed.
#       - Direction (D):
#           - Cardinal (N, S, E, W): Absolute direction (case-insensitive).
#           - Angle (<Angle): Relative angle in degrees from previous segment (or absolute from East for 1st segment).
#               Prefix with '<' (e.g., "500<90", "-200<-45").
#   - C: Optional. If present, closes the polygon to the starting point (case-insensitive).
#
# Elements (start point, segments, and 'C') are separated by one or more spaces.
WALL_DATA_STR = "0,0 5000E 3500<90 5000<90 C"
# Example of a square: "0,0 1000E 1000<90 1000<90 1000<90 C"
# Example with negative length: "0,0 -500E 500N C" (This would be 500W, then 500N, then close)


# --- Define units for easier conversion ---
INCH = 25.4 # In mm
FEET = 12 * INCH # In mm

# --- Wall Parameters (optional, default Arch values will be used if not set) ---
WALL_HEIGHT = 11 * FEET + 3 * INCH  # Example: 11 feet 3 inches high (in mm)
WALL_WIDTH = 10 * INCH    # Example: 10 inches thick (in mm)

# --- Window Parameters ---
# The window will be placed in the first wall segment (0,0) to (5000,0)
WINDOW_TYPE = "Fixed" # You can choose from presets like "Fixed", "Solid", "Sash 2-pane", "Awning", etc.
WINDOW_WIDTH = 1000  # mm
WINDOW_HEIGHT = 1200 # mm
WINDOW_SILL_HEIGHT = 900 # mm (distance from floor to bottom of window)
WINDOW_DIST_FROM_START_OF_WALL = 1500 # mm (distance from (0,0) along the wall's length)

# --- General Geometric Tolerance ---
GEOMETRIC_TOLERANCE = 1e-7 


def parse_wall_data_string(data_string):
    """Parses the WALL_DATA_STR into a structured list."""
    parts = [p.strip() for p in re.split(r'\s+', data_string) if p.strip()]
    if len(parts) < 2: 
        raise ValueError("WALL_DATA_STR is too short. Requires at least start point and one segment.")

    start_coords_str = parts[0].split(',')
    if len(start_coords_str) != 2:
        raise ValueError(f"Invalid starting point format: '{parts[0]}'. Must be 'Easting,Northing'.")
    try:
        start_x = float(start_coords_str[0])
        start_y = float(start_coords_str[1])
        start_point_xy = (start_x, start_y)
    except ValueError:
        raise ValueError(f"Invalid starting point coordinates: '{parts[0]}'. Must be numbers.")

    segments = []
    close_polygon = False

    data_segments_raw = parts[1:] 
    if data_segments_raw and data_segments_raw[-1].upper() == "C":
        close_polygon = True
        data_segments_raw = data_segments_raw[:-1] 

    segment_pattern = re.compile(r'([-+]?\d*\.?\d+)([NSWE])?(?:<([-+]?\d*\.?\d+))?$', re.IGNORECASE)

    for i, segment_str in enumerate(data_segments_raw):
        match = segment_pattern.match(segment_str)
        if not match:
            raise ValueError(f"Invalid segment format: '{segment_str}'. Expected 'LengthDirection' or 'Length<Angle'.")
        
        length_str = match.group(1)
        cardinal_dir_str = match.group(2) 
        angle_str = match.group(3)        

        try:
            length = float(length_str)
        except ValueError:
            raise ValueError(f"Invalid length value in '{segment_str}'. Must be a number.")

        direction_val = None
        if cardinal_dir_str:
            direction_val = cardinal_dir_str.upper() 
        elif angle_str is not None: 
            try:
                direction_val = float(angle_str) 
            except ValueError:
                raise ValueError(f"Invalid angle value in '{segment_str}'. Must be a number after '<'.")
        else: 
            raise ValueError(f"Segment '{segment_str}' is missing a valid direction (N,S,E,W or <Angle).")
        
        segments.append((length, direction_val))
    
    return start_point_xy, segments, close_polygon


def create_walls_from_data_string(wall_data_str):
    """
    Creates a new FreeCAD document, generates a sketch based on the parsed wall data,
    creates an Arch Wall object, and then inserts a window into the first wall segment
    using Arch.makeWindowPreset().
    """
    try:
        start_point_xy, segments_data, close_polygon_flag = parse_wall_data_string(wall_data_str)

        doc = FreeCAD.ActiveDocument
        if doc is None:
            doc = FreeCAD.newDocument("WallsWithWindowProject") 
        
        wp_placement = FreeCAD.Placement() 
        try:
            if hasattr(FreeCAD, "Gui") and FreeCAD.Gui.ActiveDocument:
                current_wp = WorkingPlane.get_working_plane()
                if hasattr(current_wp, 'get_placement') and callable(current_wp.get_placement):
                    wp_placement = current_wp.get_placement()
                else:
                    FreeCAD.Console.PrintWarning(f"Warning: 'WorkingPlane' object of type '{type(current_wp).__name__}' does not have a 'get_placement' method, defaulting to XY plane.\n")
            else:
                FreeCAD.Console.PrintMessage("Running without active GUI, defaulting to XY plane for sketch placement.\n")
        except Exception as e: 
            FreeCAD.Console.PrintWarning(f"Warning: Could not determine active working plane, defaulting to XY. Error: {e}\n")
            wp_placement = FreeCAD.Placement() 

        sketch = doc.addObject('Sketcher::SketchObject', 'WallFootprintSketch')
        sketch.Placement = wp_placement 
        
        current_point_local = FreeCAD.Vector(start_point_xy[0], start_point_xy[1], 0)
        first_point_of_wall_local = current_point_local 
        last_line_abs_angle = 0  

        sketch_segments = [] 

        for i, (length_raw, direction_or_angle) in enumerate(segments_data):
            
            length_abs = abs(length_raw)
            reverse_segment_direction = (length_raw < 0)
            
            end_point_local = None
            calculated_abs_angle = 0 

            if isinstance(direction_or_angle, str): 
                if direction_or_angle == "N": calculated_abs_angle = 90
                elif direction_or_angle == "S": calculated_abs_angle = -90 
                elif direction_or_angle == "E": calculated_abs_angle = 0
                elif direction_or_angle == "W": calculated_abs_angle = 180
            
            elif isinstance(direction_or_angle, (int, float)): 
                angle_value = direction_or_angle 

                if i == 0: 
                    calculated_abs_angle = angle_value
                else: 
                    calculated_abs_angle = last_line_abs_angle + angle_value
            
            else:
                raise ValueError(f"Unrecognized direction/angle type for segment {i+1}: {direction_or_angle}")
            
            if reverse_segment_direction:
                calculated_abs_angle = (calculated_abs_angle + 180) % 360
                if calculated_abs_angle > 180: calculated_abs_angle -= 360 
            
            last_line_abs_angle = calculated_abs_angle 

            current_angle_rad = math.radians(calculated_abs_angle)
            delta_x = length_abs * math.cos(current_angle_rad)
            delta_y = length_abs * math.sin(current_angle_rad)
            end_point_local = FreeCAD.Vector(current_point_local.x + delta_x, current_point_local.y + delta_y, 0)
            
            if end_point_local:
                sketch_segments.append(Part.LineSegment(current_point_local, end_point_local))
                current_point_local = end_point_local
            else:
                raise RuntimeError(f"Could not determine end point for segment {i+1}.")

        if close_polygon_flag:
            if current_point_local.distanceToPoint(first_point_of_wall_local) > GEOMETRIC_TOLERANCE:
                sketch_segments.append(Part.LineSegment(current_point_local, first_point_of_wall_local))
                current_point_local = first_point_of_wall_local 
            else:
                FreeCAD.Console.PrintMessage("Warning: 'C' was specified but the polygon was already closed (points are coincident within tolerance).\n")

        sketch.addGeometry(sketch_segments, False) 
        doc.recompute()
        
        # --- Create Arch Wall directly from the sketch ---
        wall_obj = Arch.makeWall(sketch) 

        wall_obj.Height = WALL_HEIGHT
        wall_obj.Width = WALL_WIDTH

        # Make the sketch invisible, as the wall is now based on it
        sketch.ViewObject.Visibility = False 
        doc.recompute() 
        
        FreeCAD.Console.PrintMessage(f"Successfully created wall object: {wall_obj.Label} from sketch.\n")

        # --- START OF AMENDED WINDOW INSERTION CODE (with correct rotation) ---
        FreeCAD.Console.PrintMessage("Attempting to insert window into the first wall segment using makeWindowPreset...\n")

        # Define the position for the window relative to the *wall's baseline*
        # X: Distance along the wall from its start (0,0 point of the baseline).
        # Y: Not used for positioning within the wall thickness by makeWindowPreset.
        # Z: Sill height (distance from floor).
        window_base_position_vec = FreeCAD.Vector(
            WINDOW_DIST_FROM_START_OF_WALL, 
            0, # Y-coordinate is often ignored by makeWindowPreset for placement
            WINDOW_SILL_HEIGHT
        )
        
        # Crucial step: Apply a 90-degree rotation around the X-axis (FreeCAD.Vector(1,0,0)).
        # This makes the internally generated window geometry stand upright from its default flat orientation.
        window_orientation_rotation = FreeCAD.Rotation(FreeCAD.Vector(1, 0, 0), 90)
        
        # Combine the position vector and the rotation into a single FreeCAD.Placement object
        window_final_placement = FreeCAD.Placement(window_base_position_vec, window_orientation_rotation)

        # Create the Arch Window using makeWindowPreset
        # All required positional arguments (h1-o2) are included.
        window_obj = Arch.makeWindowPreset(
            WINDOW_TYPE, 
            width=WINDOW_WIDTH,
            height=WINDOW_HEIGHT,
            h1=100, h2=100, h3=100, w1=200, w2=100, o1=0, o2=100, 
            placement=window_final_placement # Use the placement with correct rotation
        )

        # Host the window in the wall. This is crucial for it to cut the opening.
        window_obj.Hosts = [wall_obj]
        window_obj.Label = "MyWindow"

        doc.recompute() # Recompute to apply window changes

        FreeCAD.Console.PrintMessage(f"Successfully created window object: {window_obj.Label}.\n")
        # --- END OF AMENDED WINDOW INSERTION CODE ---


        # If running in GUI, fit all contents to view for better visualization
        if hasattr(FreeCAD, "Gui") and FreeCAD.Gui.ActiveDocument:
            FreeCAD.Gui.ActiveDocument.ActiveView.fitAll()

    except Exception as e:
        FreeCAD.Console.PrintError(f"An error occurred: {e}\n")
        import traceback
        traceback.print_exc()

# Run the macro
create_walls_from_data_string(WALL_DATA_STR)
